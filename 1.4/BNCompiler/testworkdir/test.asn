-- test.asn --

TEST_ASN

DEFINITIONS IMPLICIT TAGS ::= BEGIN

EXPORTS TestOCT,TestPRN,TestI32,TestI16,TestI8,ContentType,ValueWithParams,ParamsMap,ContentPartHeaders,ContentPartHeader,ContentSchema,Data,DataArray;
	-- --

	TestIR  ::= INTEGER (1 .. 5)
	TestI8	::= INTEGER (0 .. 255)
	TestI14 ::= INTEGER (0 .. 16384)
	TestI16	::= INTEGER (0 .. 65535)
	TestI32	::= INTEGER (0 .. 4294967295)	
	TestI	::= INTEGER
	TestNI  ::= INTEGER (-128 .. 128)
	TestNI2  ::= INTEGER (-2048 .. 2048)

	TestPRN	::= PrintableString
	TestOCT	::= OCTET STRING

	
	Data   ::= CHOICE {
		plain 		[0] TestPRN, 
		unicode		[1] TestOCT, 
		binary		[2] TestOCT,
		simpleType	[3] PrintableString,
		simpleOctType	[4] OCTET STRING,
		booleanType	[5] BOOLEAN,
		intType		[6] INTEGER,
		intBndType	[7] INTEGER (0 .. 255)		
	}

	DataArray ::= SEQUENCE OF Data

	DataSeq   ::= SEQUENCE {
		plain 		[0] TestPRN, 
		unicode		[1] TestOCT OPTIONAL, 
		binary		[2] TestOCT,
		simpleType	[3] PrintableString,
		simpleOctType   OCTET STRING,
		booleanType	[5] BOOLEAN,
		intType		[6] INTEGER,
		intBndType	[7] INTEGER (0 .. 255),
		stringArray	[8] SEQUENCE OF PrintableString,
		dataArray	[9] SEQUENCE OF Data,
		extension	ANY OPTIONAL
	}	

	DataSeqMO ::= SEQUENCE {
		plain 		[0] TestPRN, 
		unicode		[1] TestOCT OPTIONAL, 
		binary		[2] TestOCT OPTIONAL,
		simpleType	[3] PrintableString OPTIONAL,
		simpleOctType   OCTET STRING,
		booleanType	[5] BOOLEAN OPTIONAL,
		intType		[6] INTEGER OPTIONAL,
		intBndType	[7] INTEGER (0 .. 255) OPTIONAL,
		stringArray	[8] SEQUENCE OF PrintableString OPTIONAL,
		dataArray	[9] SEQUENCE OF Data OPTIONAL,
		plain2 		[10] TestPRN OPTIONAL, 
		unicode2	[18] TestOCT OPTIONAL, 
		binary2		[11] TestOCT OPTIONAL,
		simpleType2	[12] PrintableString OPTIONAL,
		simpleOctType2   OCTET STRING OPTIONAL,
		booleanType2	[13] BOOLEAN OPTIONAL,
		intType2	[19] INTEGER OPTIONAL,
		intBndType2	[14] INTEGER (0 .. 255) OPTIONAL,
		stringArray2	[15] SEQUENCE OF PrintableString OPTIONAL,
		dataArray2	[16] SEQUENCE OF Data OPTIONAL,
		plain3 		[17] TestPRN OPTIONAL
	}


	DataSeqArray ::= SEQUENCE OF DataSeq
	StringArray ::= SEQUENCE OF PrintableString
	OctetStringArray ::= SEQUENCE OF OCTET STRING

	ITUType1 ::= VisibleString
	ITUType2 ::= [APPLICATION 3] IMPLICIT ITUType1
	ITUType3 ::= [2] ITUType2
	ITUType4 ::= [APPLICATION 7] IMPLICIT ITUType3
	ITUType5 ::= [2] IMPLICIT ITUType2	
	ITUType6 ::= [9] VisibleString

	ITUSequence ::= SEQUENCE {
		type1  VisibleString,
		type2  [APPLICATION 3] IMPLICIT ITUType1,
		type3  [2] ITUType2,
		type4  [APPLICATION 7] IMPLICIT ITUType3,
		type5  [2] IMPLICIT ITUType2 OPTIONAL,
		type6  [7] VisibleString,
		type7  [8] ITUType6
	}

	NullSequence ::= NULL
	TaggedNullSequence ::= [1] NULL

	SequenceWithNull ::= SEQUENCE {
		test	PrintableString,
		nullVal	NULL,
		test2	[1] PrintableString
	}


	TaggedSequence ::= [APPLICATION 8] SEQUENCE {
		type1  [7] VisibleString OPTIONAL
	}


	ValueWithParams ::= SEQUENCE
	{
		value		[0]	PrintableString,			-- Значение
		params		[1]	SEQUENCE OF PlainParamsMap OPTIONAL	-- Текстовые параметры
	}

	PlainParamsMap ::= SEQUENCE
	{
		param_name	[1]	PrintableString,
		param_value	[2]	PrintableString
	}

	ContentPartHeader ::= SEQUENCE
	{
		name		[0]	PrintableString,		
		values		[1]	SEQUENCE OF ValueWithParams
	}

	ContentPartHeaders ::= SEQUENCE OF ContentPartHeader

	-- * Тип контента * --
	ContentType ::= ENUMERATED {
		text_any						(100),
		text_html						(101),
		text_plain						(102),
		audio_x_midi						(306), -- extension *.mid;*.midi
		video_any						(400),
		video_mpeg						(401), -- extension *.mpg;*.mpeg
		video_avi						(402), -- extension *.avi
		video_quicktime						(403), -- extension *.qt;*.mov
		video_x_msvideo						(404), -- extension *.avi
		application_smil					(500)  -- SMIL
	}

	ContentSchema ::= ENUMERATED {
		multipart_any						(110),
		multipart_mixed						(111),
		multipart_form_data					(112),
		multipart_byteranges					(113),
		multipart_alternative					(114),
		multipart_related					(175)		
	}

	SequenceWithEnum ::= SEQUENCE {
		item		PrintableString,
		enval		ContentSchema,
		taggedEnval	[1] ContentSchema
	}
	
	TestRecursiveDefinetion ::= SEQUENCE
	{
		name			[1]	PrintableString,
		value			[2]	TestRecursiveDefinetion OPTIONAL
	}

	SequenceWithDefault ::= SEQUENCE {
		nodefault		[0] INTEGER,
		withDefault		[1] PrintableString DEFAULT "dd",
		withIntDef 		[2] INTEGER DEFAULT 120,
		withSeqDef		[3] SEQUENCE {
			name	PrintableString,
			email	PrintableString
		}
		DEFAULT { name "Name", email "Email"},
		withOctDef		[4] TestOCT DEFAULT '01101100'B,
		withOctDef2		[5] OCTET STRING DEFAULT 'FFEEAA'H,
		withSeqOf		[6] SEQUENCE OF PrintableString DEFAULT { "aa","dd" },
		withSeqOf2		[7] SEQUENCE OF TestPRN DEFAULT { "cc","ee" },
		withSeqOf3		[8] StringArray DEFAULT { "fff","ggg" }
	}

	SetWithDefault ::= SET {
		nodefault		[2] INTEGER,
		nodefault2		[1] TestPRN,
		default3		[3] PrintableString DEFAULT "DDDdd"
	}

	TestSequenceWithNonames ::= SEQUENCE {
		seq	[0] SEQUENCE {
			it1 INTEGER OPTIONAL
		},
		ch	[1] CHOICE {
			it1 [0] INTEGER,
			it2 [1] OCTET STRING
		},
		seqf	[2] SEQUENCE OF SEQUENCE {
			it1 INTEGER OPTIONAL
		}
	}


	SetOfTest	::= SET OF Data

	TestBitStr	::= BIT STRING

	TestBitStrBnd	::= BIT STRING(SIZE(1..16))

	TestUnicodeStr	::= UTF8String

	TestUnicodeStrBnd ::= UTF8String(SIZE(12))

	TestSequenceV12 ::= SEQUENCE {
		attrSimple	[0] PrintableString,
		attrStr		[1] PrintableString (SIZE(1..4)),
		attrStr2	[2] TestPRN,
		attrArr		[3] SEQUENCE SIZE(1..5) OF PrintableString,
		attrBitStr	[4] BIT STRING OPTIONAL,
		attrBitStrDef	[4] BIT STRING DEFAULT '011'B,
		attrBitStrBnd	[5] BIT STRING(SIZE(1..36)) OPTIONAL,
		attrBoxBitStr	[6] TestBitStrBnd OPTIONAL,
		attrStrict	[7] OCTET STRING(SIZE(4))
	}

    	BugPrimitive ::= CHOICE
    	{
      		bugBoolean [0] BOOLEAN,
      		bugInteger [1] INTEGER
    	}

    	BugEnum ::= INTEGER

    	BugSequenceType ::= SEQUENCE
    	{
      		booleanField [0] BOOLEAN,
      		integerField [0] INTEGER
    	}

    	BugValueType ::= CHOICE
    	{
      		bugPrimitive [0] BugPrimitive,
      		bugEnum      [1] BugEnum,
      		bugSequence  [2] BugSequenceType
    	}

    	BugList ::= SEQUENCE OF BugValueType

	TaggedSeqInSeq ::= [APPLICATION 4] SEQUENCE 
	{
		field [0] PlainParamsMap
	}

	TestReal ::= REAL

	TestGT ::= GeneralizedTime

	TestUTC ::= UTCTime

	TestLong ::= INTEGER(1 .. 2247483648)


	TestSeqV13 ::= SEQUENCE 
	{
		field1 [0] REAL,
		fieldI INTEGER,
		field2 TestReal,
		field3 REAL OPTIONAL,
		field4 [1] REAL,
		field5 GeneralizedTime,
		field6 UTCTime,
		field7 TestLong
	}

	TestLongTag ::= [APPLICATION 15123] INTEGER
	TestLongTag2 ::= [APPLICATION 40] INTEGER

	TestSimpleSequence ::= SEQUENCE
	{
		field1 [0] INTEGER,
		field2 [1] UTF8String,
		field3 [2] UTF8String
	}
END
